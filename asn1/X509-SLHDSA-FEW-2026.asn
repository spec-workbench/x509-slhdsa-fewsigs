X509-SLH-DSA-FEW-Module-2026
  { iso(1) identified-organization(3) dod(6) internet(1) security(5)
    mechanisms(5) pkix(7) id-mod(0)
    id-mod-x509-slh-dsa-few-2026(TBD0) }

DEFINITIONS IMPLICIT TAGS ::= BEGIN

EXPORTS ALL;

IMPORTS
  PUBLIC-KEY, SIGNATURE-ALGORITHM, SMIME-CAPS
    FROM AlgorithmInformation-2009  -- in [RFC5912]
    { iso(1) identified-organization(3) dod(6) internet(1)
      security(5) mechanisms(5) pkix(7) id-mod(0)
      id-mod-algorithmInformation-02(58) } ;

--
-- Object identifiers for the SLH-DSA-FEW parameter sets; see
-- [SP800-230]. TBD1 to TBD12 are to be assigned by NIST in [CSOR].
--

nistAlgorithms OBJECT IDENTIFIER ::= { joint-iso-itu-t(2)
  country(16) us(840) organization(1) gov(101) csor(3) 4 }

sigAlgs OBJECT IDENTIFIER ::= { nistAlgorithms 3 }

--
-- Pure SLH-DSA-FEW object identifiers
--

id-slh-dsa-sha2-128-24 OBJECT IDENTIFIER ::= { sigAlgs TBD1 }

id-slh-dsa-shake-128-24 OBJECT IDENTIFIER ::= { sigAlgs TBD2 }

id-slh-dsa-sha2-192-24 OBJECT IDENTIFIER ::= { sigAlgs TBD3 }

id-slh-dsa-shake-192-24 OBJECT IDENTIFIER ::= { sigAlgs TBD4 }

id-slh-dsa-sha2-256-24 OBJECT IDENTIFIER ::= { sigAlgs TBD5 }

id-slh-dsa-shake-256-24 OBJECT IDENTIFIER ::= { sigAlgs TBD6 }

--
-- HashSLH-DSA-FEW object identifiers
--

id-hash-slh-dsa-sha2-128-24-with-sha256 OBJECT IDENTIFIER ::= {
  sigAlgs TBD7 }

id-hash-slh-dsa-shake-128-24-with-shake128 OBJECT IDENTIFIER ::= {
  sigAlgs TBD8 }

id-hash-slh-dsa-sha2-192-24-with-sha512 OBJECT IDENTIFIER ::= {
  sigAlgs TBD9 }

id-hash-slh-dsa-shake-192-24-with-shake256 OBJECT IDENTIFIER ::= {
  sigAlgs TBD10 }

id-hash-slh-dsa-sha2-256-24-with-sha512 OBJECT IDENTIFIER ::= {
  sigAlgs TBD11 }

id-hash-slh-dsa-shake-256-24-with-shake256 OBJECT IDENTIFIER ::= {
  sigAlgs TBD12 }

--
-- Pure SLH-DSA-FEW public key identifiers
--

pk-slh-dsa-sha2-128-24 PUBLIC-KEY ::= {
  IDENTIFIER id-slh-dsa-sha2-128-24
  -- KEY no ASN.1 wrapping --
  CERT-KEY-USAGE
      { digitalSignature, nonRepudiation, keyCertSign, cRLSign }
  -- PRIVATE-KEY no ASN.1 wrapping -- }

pk-slh-dsa-shake-128-24 PUBLIC-KEY ::= {
  IDENTIFIER id-slh-dsa-shake-128-24
  -- KEY no ASN.1 wrapping --
  CERT-KEY-USAGE
      { digitalSignature, nonRepudiation, keyCertSign, cRLSign }
  -- PRIVATE-KEY no ASN.1 wrapping -- }

pk-slh-dsa-sha2-192-24 PUBLIC-KEY ::= {
  IDENTIFIER id-slh-dsa-sha2-192-24
  -- KEY no ASN.1 wrapping --
  CERT-KEY-USAGE
      { digitalSignature, nonRepudiation, keyCertSign, cRLSign }
  -- PRIVATE-KEY no ASN.1 wrapping -- }

pk-slh-dsa-shake-192-24 PUBLIC-KEY ::= {
  IDENTIFIER id-slh-dsa-shake-192-24
  -- KEY no ASN.1 wrapping --
  CERT-KEY-USAGE
      { digitalSignature, nonRepudiation, keyCertSign, cRLSign }
  -- PRIVATE-KEY no ASN.1 wrapping -- }

pk-slh-dsa-sha2-256-24 PUBLIC-KEY ::= {
  IDENTIFIER id-slh-dsa-sha2-256-24
  -- KEY no ASN.1 wrapping --
  CERT-KEY-USAGE
      { digitalSignature, nonRepudiation, keyCertSign, cRLSign }
  -- PRIVATE-KEY no ASN.1 wrapping -- }

pk-slh-dsa-shake-256-24 PUBLIC-KEY ::= {
  IDENTIFIER id-slh-dsa-shake-256-24
  -- KEY no ASN.1 wrapping --
  CERT-KEY-USAGE
      { digitalSignature, nonRepudiation, keyCertSign, cRLSign }
  -- PRIVATE-KEY no ASN.1 wrapping -- }

--
-- HashSLH-DSA-FEW public key identifiers
--

pk-hash-slh-dsa-sha2-128-24-with-sha256 PUBLIC-KEY ::= {
  IDENTIFIER id-hash-slh-dsa-sha2-128-24-with-sha256
  -- KEY no ASN.1 wrapping --
  CERT-KEY-USAGE
      { digitalSignature, nonRepudiation, keyCertSign, cRLSign }
  -- PRIVATE-KEY no ASN.1 wrapping -- }

pk-hash-slh-dsa-shake-128-24-with-shake128 PUBLIC-KEY ::= {
  IDENTIFIER id-hash-slh-dsa-shake-128-24-with-shake128
  -- KEY no ASN.1 wrapping --
  CERT-KEY-USAGE
      { digitalSignature, nonRepudiation, keyCertSign, cRLSign }
  -- PRIVATE-KEY no ASN.1 wrapping -- }

pk-hash-slh-dsa-sha2-192-24-with-sha512 PUBLIC-KEY ::= {
  IDENTIFIER id-hash-slh-dsa-sha2-192-24-with-sha512
  -- KEY no ASN.1 wrapping --
  CERT-KEY-USAGE
      { digitalSignature, nonRepudiation, keyCertSign, cRLSign }
  -- PRIVATE-KEY no ASN.1 wrapping -- }

pk-hash-slh-dsa-shake-192-24-with-shake256 PUBLIC-KEY ::= {
  IDENTIFIER id-hash-slh-dsa-shake-192-24-with-shake256
  -- KEY no ASN.1 wrapping --
  CERT-KEY-USAGE
      { digitalSignature, nonRepudiation, keyCertSign, cRLSign }
  -- PRIVATE-KEY no ASN.1 wrapping -- }

pk-hash-slh-dsa-sha2-256-24-with-sha512 PUBLIC-KEY ::= {
  IDENTIFIER id-hash-slh-dsa-sha2-256-24-with-sha512
  -- KEY no ASN.1 wrapping --
  CERT-KEY-USAGE
      { digitalSignature, nonRepudiation, keyCertSign, cRLSign }
  -- PRIVATE-KEY no ASN.1 wrapping -- }

pk-hash-slh-dsa-shake-256-24-with-shake256 PUBLIC-KEY ::= {
  IDENTIFIER id-hash-slh-dsa-shake-256-24-with-shake256
  -- KEY no ASN.1 wrapping --
  CERT-KEY-USAGE
      { digitalSignature, nonRepudiation, keyCertSign, cRLSign }
  -- PRIVATE-KEY no ASN.1 wrapping -- }

--
-- Pure SLH-DSA-FEW signature algorithm identifiers
--

sa-slh-dsa-sha2-128-24 SIGNATURE-ALGORITHM ::= {
  IDENTIFIER id-slh-dsa-sha2-128-24
  PARAMS ARE absent
  PUBLIC-KEYS { pk-slh-dsa-sha2-128-24 }
  SMIME-CAPS {
    IDENTIFIED BY id-slh-dsa-sha2-128-24 } }

sa-slh-dsa-shake-128-24 SIGNATURE-ALGORITHM ::= {
  IDENTIFIER id-slh-dsa-shake-128-24
  PARAMS ARE absent
  PUBLIC-KEYS { pk-slh-dsa-shake-128-24 }
  SMIME-CAPS {
    IDENTIFIED BY id-slh-dsa-shake-128-24 } }

sa-slh-dsa-sha2-192-24 SIGNATURE-ALGORITHM ::= {
  IDENTIFIER id-slh-dsa-sha2-192-24
  PARAMS ARE absent
  PUBLIC-KEYS { pk-slh-dsa-sha2-192-24 }
  SMIME-CAPS {
    IDENTIFIED BY id-slh-dsa-sha2-192-24 } }

sa-slh-dsa-shake-192-24 SIGNATURE-ALGORITHM ::= {
  IDENTIFIER id-slh-dsa-shake-192-24
  PARAMS ARE absent
  PUBLIC-KEYS { pk-slh-dsa-shake-192-24 }
  SMIME-CAPS {
    IDENTIFIED BY id-slh-dsa-shake-192-24 } }

sa-slh-dsa-sha2-256-24 SIGNATURE-ALGORITHM ::= {
  IDENTIFIER id-slh-dsa-sha2-256-24
  PARAMS ARE absent
  PUBLIC-KEYS { pk-slh-dsa-sha2-256-24 }
  SMIME-CAPS {
    IDENTIFIED BY id-slh-dsa-sha2-256-24 } }

sa-slh-dsa-shake-256-24 SIGNATURE-ALGORITHM ::= {
  IDENTIFIER id-slh-dsa-shake-256-24
  PARAMS ARE absent
  PUBLIC-KEYS { pk-slh-dsa-shake-256-24 }
  SMIME-CAPS {
    IDENTIFIED BY id-slh-dsa-shake-256-24 } }

--
-- HashSLH-DSA-FEW signature algorithm identifiers
--

sa-hash-slh-dsa-sha2-128-24-with-sha256 SIGNATURE-ALGORITHM ::= {
  IDENTIFIER id-hash-slh-dsa-sha2-128-24-with-sha256
  PARAMS ARE absent
  PUBLIC-KEYS { pk-hash-slh-dsa-sha2-128-24-with-sha256 }
  SMIME-CAPS {
    IDENTIFIED BY id-hash-slh-dsa-sha2-128-24-with-sha256 } }

sa-hash-slh-dsa-shake-128-24-with-shake128 SIGNATURE-ALGORITHM ::= {
  IDENTIFIER id-hash-slh-dsa-shake-128-24-with-shake128
  PARAMS ARE absent
  PUBLIC-KEYS { pk-hash-slh-dsa-shake-128-24-with-shake128 }
  SMIME-CAPS {
    IDENTIFIED BY id-hash-slh-dsa-shake-128-24-with-shake128 } }

sa-hash-slh-dsa-sha2-192-24-with-sha512 SIGNATURE-ALGORITHM ::= {
  IDENTIFIER id-hash-slh-dsa-sha2-192-24-with-sha512
  PARAMS ARE absent
  PUBLIC-KEYS { pk-hash-slh-dsa-sha2-192-24-with-sha512 }
  SMIME-CAPS {
    IDENTIFIED BY id-hash-slh-dsa-sha2-192-24-with-sha512 } }

sa-hash-slh-dsa-shake-192-24-with-shake256 SIGNATURE-ALGORITHM ::= {
  IDENTIFIER id-hash-slh-dsa-shake-192-24-with-shake256
  PARAMS ARE absent
  PUBLIC-KEYS { pk-hash-slh-dsa-shake-192-24-with-shake256 }
  SMIME-CAPS {
    IDENTIFIED BY id-hash-slh-dsa-shake-192-24-with-shake256 } }

sa-hash-slh-dsa-sha2-256-24-with-sha512 SIGNATURE-ALGORITHM ::= {
  IDENTIFIER id-hash-slh-dsa-sha2-256-24-with-sha512
  PARAMS ARE absent
  PUBLIC-KEYS { pk-hash-slh-dsa-sha2-256-24-with-sha512 }
  SMIME-CAPS {
    IDENTIFIED BY id-hash-slh-dsa-sha2-256-24-with-sha512 } }

sa-hash-slh-dsa-shake-256-24-with-shake256 SIGNATURE-ALGORITHM ::= {
  IDENTIFIER id-hash-slh-dsa-shake-256-24-with-shake256
  PARAMS ARE absent
  PUBLIC-KEYS { pk-hash-slh-dsa-shake-256-24-with-shake256 }
  SMIME-CAPS {
    IDENTIFIED BY id-hash-slh-dsa-shake-256-24-with-shake256 } }

--
-- Expand SignatureAlgorithms from [RFC5912]
--

SignatureAlgorithms SIGNATURE-ALGORITHM ::= {
  sa-slh-dsa-sha2-128-24 |
  sa-slh-dsa-shake-128-24 |
  sa-slh-dsa-sha2-192-24 |
  sa-slh-dsa-shake-192-24 |
  sa-slh-dsa-sha2-256-24 |
  sa-slh-dsa-shake-256-24 |
  sa-hash-slh-dsa-sha2-128-24-with-sha256 |
  sa-hash-slh-dsa-shake-128-24-with-shake128 |
  sa-hash-slh-dsa-sha2-192-24-with-sha512 |
  sa-hash-slh-dsa-shake-192-24-with-shake256 |
  sa-hash-slh-dsa-sha2-256-24-with-sha512 |
  sa-hash-slh-dsa-shake-256-24-with-shake256,
  ... }

--
-- Expand SMimeCaps from [RFC5912]
--

SMimeCaps SMIME-CAPS ::= {
  sa-slh-dsa-sha2-128-24.&smimeCaps |
  sa-slh-dsa-shake-128-24.&smimeCaps |
  sa-slh-dsa-sha2-192-24.&smimeCaps |
  sa-slh-dsa-shake-192-24.&smimeCaps |
  sa-slh-dsa-sha2-256-24.&smimeCaps |
  sa-slh-dsa-shake-256-24.&smimeCaps |
  sa-hash-slh-dsa-sha2-128-24-with-sha256.&smimeCaps |
  sa-hash-slh-dsa-shake-128-24-with-shake128.&smimeCaps |
  sa-hash-slh-dsa-sha2-192-24-with-sha512.&smimeCaps |
  sa-hash-slh-dsa-shake-192-24-with-shake256.&smimeCaps |
  sa-hash-slh-dsa-sha2-256-24-with-sha512.&smimeCaps |
  sa-hash-slh-dsa-shake-256-24-with-shake256.&smimeCaps,
  ... }

--
-- Expand PublicKeyAlgorithms from [RFC5912]
--

PublicKeyAlgorithms PUBLIC-KEY ::= {
  pk-slh-dsa-sha2-128-24 |
  pk-slh-dsa-shake-128-24 |
  pk-slh-dsa-sha2-192-24 |
  pk-slh-dsa-shake-192-24 |
  pk-slh-dsa-sha2-256-24 |
  pk-slh-dsa-shake-256-24 |
  pk-hash-slh-dsa-sha2-128-24-with-sha256 |
  pk-hash-slh-dsa-shake-128-24-with-shake128 |
  pk-hash-slh-dsa-sha2-192-24-with-sha512 |
  pk-hash-slh-dsa-shake-192-24-with-shake256 |
  pk-hash-slh-dsa-sha2-256-24-with-sha512 |
  pk-hash-slh-dsa-shake-256-24-with-shake256,
  ... }

END
